FME workspace PSMA_AB_LGA_Builder.fmw

Parameters:
- SourceDataset_ESRISHAPE = C:\Users\Toby\Downloads\MAY16_AdminBounds_ESRIShapefileorDBFfile_20160523140152\Administrative Boundaries\Local Government Areas MAY 2016\Standard\*_LGA_POLYGON_shp.shp   # Source Esri Shapefile(s)
- FEATURE_TYPES =
- SourceDataset_DBF = C:\Users\Toby\Downloads\MAY16_AdminBounds_ESRIShapefileorDBFfile_20160523140152\Administrative Boundaries\Local Government Areas MAY 2016\Standard\*_LGA_shp.dbf   # Source dBASE (DBF) File(s)
- FEATURE_TYPES_2 =
- DestDataset_ESRISHAPE = C:\Users\Toby\Downloads   # Destination Esri Shapefile Folder

Readers:
- ESRISHAPE_1: ESRISHAPE from $(SourceDataset_ESRISHAPE)
- DBF_1: DBF from $(SourceDataset_DBF)

Writers:
- ESRISHAPE_2: ESRISHAPE to $(DestDataset_ESRISHAPE)

NSW_LGA_POLYGON_shp (reader ESRISHAPE_1)
    attributes: LG_PLY_PID char(15), DT_CREATE date, DT_RETIRE date, LGA_PID char(15)
    -> FeatureMerger [REQUESTOR]
NSW_LGA_shp (reader DBF_1)
    attributes: LGA_PID char(15), DT_CREATE date, DT_RETIRE date, LGA_NAME char(100), ABB_NAME char(100), DT_GAZETD date, STATE_PID char(15)
    -> AttributeValueMapper
AttributeValueMapper
    VAL_ATTR = STATE_NAME
    DIRECTION = Forward (Source To Destination)
    LUT = 1,NSW,2,VIC,3,QLD,4,SA,5,WA,6,TAS,7,NT,8,ACT
    SRC = STATE_PID
    -> StringConcatenator
StringConcatenator
    PARM_LINE = @FullTitleCase(@Value(ABB_NAME)) (@Value(STATE_NAME))
    ATTRLIST = ABB_NAME
    ACTION = Overwrite Existing Attributes
    -> FeatureMerger [SUPPLIER]
FeatureMerger
    JOIN_KEYS = @Value(LGA_PID) @Value(LGA_PID) AUTO
    SUPPLIERS_FIRST = No
    IGNORE_NULLS = No
    ATTR_CONFLICT_RES = Use Requestor
    REJECT_NULL_MISSING_KEYS = No
    MERGE_TYPE = Attributes Only
    ATTR_ACCUM_MODE = Merge Supplier
    GROUP_BY = LGA_PID
    PROCESS_DUPS = No
    MERGED -> Aggregator
Aggregator
    AGGREGATE_TYPE = Homogeneous Collection (If Possible)
    ACCUM_ATTRS_NAME = Get Attributes From One Representative Feature
    SEP = ,
    ORDERED = No
    GROUP_BY = LGA_PID
    MODE = Geometry - Assemble One Level
    AGGREGATE -> AUST_LGA_POLYGON_May16 (writer ESRISHAPE_2)
AUST_LGA_POLYGON_May16 (writer ESRISHAPE_2)
    attributes: LGA_PID char(15), DT_CREATE date, DT_RETIRE date, LGA_NAME char(100), ABB_NAME char(100), DT_GAZETD date, STATE_PID char(15)
