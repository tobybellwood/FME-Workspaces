FME workspace PSMA_AB_StateElectorate_Builder.fmw

Parameters:
- DestDataset_ESRISHAPE = C:\Users\Toby\Downloads   # Destination Esri Shapefile Folder
- SourceDataset_ESRISHAPE = C:\Users\Toby\Downloads\MAY16_AdminBounds_ESRIShapefileorDBFfile_20160523140152\Administrative Boundaries\State Electoral Boundaries MAY 2016\Standard\*_STATE_ELECTORAL_POLYGON_shp.shp   # Source Esri Shapefile(s)
- FEATURE_TYPES =
- SourceDataset_DBF = C:\Users\Toby\Downloads\MAY16_AdminBounds_ESRIShapefileorDBFfile_20160523140152\Administrative Boundaries\State Electoral Boundaries MAY 2016\Standard\*_STATE_ELECTORAL_shp.dbf   # Source dBASE (DBF) File(s)
- FEATURE_TYPES_2 =

Readers:
- ESRISHAPE_1: ESRISHAPE from $(SourceDataset_ESRISHAPE)
- DBF_1: DBF from $(SourceDataset_DBF)

Writers:
- ESRISHAPE_2: ESRISHAPE to $(DestDataset_ESRISHAPE)

ACT_STATE_ELECTORAL_POLYGON_shp (reader ESRISHAPE_1)
    attributes: SE_PLY_PID char(15), DT_CREATE date, DT_RETIRE date, SE_PID char(15)
    -> FeatureMerger [REQUESTOR]
ACT_STATE_ELECTORAL_shp (reader DBF_1)
    attributes: SE_PID char(15), DT_CREATE date, DT_RETIRE date, NAME char(50), DT_GAZETD date, EFF_START date, EFF_END date, STATE_PID char(15), SECL_CODE char(10)
    -> AttributeValueMapper
AttributeValueMapper
    VAL_ATTR = STATE_NAME
    DIRECTION = Forward (Source To Destination)
    LUT = 1,NSW,2,VIC,3,QLD,4,SA,5,WA,6,TAS,7,NT,8,ACT
    SRC = STATE_PID
    -> StringReplacer
StringReplacer
    SRC_ATTRS = NAME
    NO_MATCH = _FME_NO_OP_
    CASE = NO
    FIND_TEXT = ,+.*
    REGEXP = YES
    -> StringConcatenator
StringConcatenator
    ACTION = Overwrite Existing Attributes
    ATTRLIST = NAME
    PARM_LINE = @Value(NAME) (@Value(STATE_NAME))
    -> FeatureMerger [SUPPLIER]
FeatureMerger
    JOIN_KEYS = @Value(SE_PID) @Value(SE_PID) AUTO
    IGNORE_NULLS = No
    REJECT_NULL_MISSING_KEYS = No
    ATTR_ACCUM_MODE = Merge Supplier
    MERGE_TYPE = Attributes Only
    GROUP_BY = SE_PID
    ATTR_CONFLICT_RES = Use Requestor
    PROCESS_DUPS = No
    SUPPLIERS_FIRST = No
    MERGED -> Aggregator_4
Aggregator_4
    SEP = ,
    GROUP_BY = SE_PID
    AGGREGATE_TYPE = Homogeneous Collection (If Possible)
    ORDERED = No
    ACCUM_ATTRS_NAME = Get Attributes From One Representative Feature
    MODE = Geometry - Assemble One Level
    AGGREGATE -> TimeStamper
TimeStamper
    FMT = FME Date (^Y^m^d)
    TIME_ATTR = _timestamp
    -> TestFilter
TestFilter
    DEFAULT_VALUE = <UNFILTERED>
    TEST_LIST:
      BOOL_OP,AND,COMPOSITE_TEST,<Unused>,TEST_CLAUSE,"TEST @Value(EFF_END) < @Value(_timestamp)
      TEST @Value(EFF_END) > 00000000",Past,BOOL_OP,AND,COMPOSITE_TEST,<Unused>,TEST_CLAUSE,"TEST @Value(EFF_START) > @Value(_timestamp)
      TEST @Value(SECL_CODE) IN 1,2",Finalised,BOOL_OP,AND,COMPOSITE_TEST,<Unused>,TEST_CLAUSE,"TEST @Value(SECL_CODE) IN 1,2",LowerCurrent,BOOL_OP,AND,COMPOSITE_TEST,<Unused>,TEST_CLAUSE,"TEST @Value(SECL_CODE) = 3",UpperCurrent
    Finalised -> AUST_STE_ELB_future_POLYGON_May16 (writer ESRISHAPE_2)
    LowerCurrent -> AUST_STE_ELB_Lower_POLYGON_May16 (writer ESRISHAPE_2)
    UpperCurrent -> AUST_STE_ELB_Upper_POLYGON_May16 (writer ESRISHAPE_2)
AUST_STE_ELB_future_POLYGON_May16 (writer ESRISHAPE_2)
    attributes: SE_PID char(15), DT_CREATE date, DT_RETIRE date, NAME char(50), DT_GAZETD date, EFF_START date, EFF_END date, STATE_PID char(15), SECL_CODE char(10)
AUST_STE_ELB_Lower_POLYGON_May16 (writer ESRISHAPE_2)
    attributes: SE_PID char(15), DT_CREATE date, DT_RETIRE date, NAME char(50), DT_GAZETD date, EFF_START date, EFF_END date, STATE_PID char(15), SECL_CODE char(10)
AUST_STE_ELB_Upper_POLYGON_May16 (writer ESRISHAPE_2)
    attributes: SE_PID char(15), DT_CREATE date, DT_RETIRE date, NAME char(50), DT_GAZETD date, EFF_START date, EFF_END date, STATE_PID char(15), SECL_CODE char(10)
