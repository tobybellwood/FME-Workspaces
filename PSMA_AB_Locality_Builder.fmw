FME workspace PSMA_AB_Locality_Builder.fmw

Parameters:
- DestDataset_ESRISHAPE = C:\Users\Toby\Downloads   # Destination Esri Shapefile Folder
- SourceDataset_ESRISHAPE = C:\Users\Toby\Downloads\MAY16_AdminBounds_ESRIShapefileorDBFfile_20160523140152\Administrative Boundaries\Suburbs - Localities MAY 2016\Standard\*_LOCALITY_POLYGON_shp.shp   # Source Esri Shapefile(s)
- FEATURE_TYPES =
- SourceDataset_DBF = C:\Users\Toby\Downloads\MAY16_AdminBounds_ESRIShapefileorDBFfile_20160523140152\Administrative Boundaries\Suburbs - Localities MAY 2016\Standard\*_LOCALITY_shp.dbf   # Source dBASE (DBF) File(s)
- FEATURE_TYPES_2 =

Readers:
- ESRISHAPE_1: ESRISHAPE from $(SourceDataset_ESRISHAPE)
- DBF_1: DBF from $(SourceDataset_DBF)

Writers:
- ESRISHAPE_2: ESRISHAPE to $(DestDataset_ESRISHAPE)

ACT_LOCALITY_POLYGON_shp (reader ESRISHAPE_1)
    attributes: LC_PLY_PID char(15), DT_CREATE date, DT_RETIRE date, LOC_PID char(15)
    -> FeatureMerger [REQUESTOR]
ACT_LOCALITY_shp (reader DBF_1)
    attributes: LOC_PID char(15), DT_CREATE date, DT_RETIRE date, NAME char(100), POSTCODE char(4), PRIM_PCODE char(4), LOCCL_CODE char(1), DT_GAZETD date, STATE_PID char(15)
    -> FeatureMerger [SUPPLIER]
FeatureMerger
    GROUP_BY = LOC_PID
    ATTR_ACCUM_MODE = Merge Supplier
    MERGE_TYPE = Attributes Only
    ATTR_CONFLICT_RES = Use Requestor
    PROCESS_DUPS = No
    JOIN_KEYS = @Value(LOC_PID) @Value(LOC_PID) AUTO
    SUPPLIERS_FIRST = No
    REJECT_NULL_MISSING_KEYS = No
    IGNORE_NULLS = No
    MERGED -> AttributeFilter
AttributeFilter
    ATTR_VALUES = <EMPTY>,<MISSING>,<NULL>,<UNFILTERED>,D,G,H
    ATTR_NAME = LOCCL_CODE
    G -> Aggregator
Aggregator
    GROUP_BY = LOC_PID
    ACCUM_ATTRS_NAME = Get Attributes From One Representative Feature
    SEP = ,
    MODE = Geometry - Assemble One Level
    ORDERED = No
    AGGREGATE_TYPE = Homogeneous Collection (If Possible)
    AGGREGATE -> AUST_LOCALITY_POLYGON_May16 (writer ESRISHAPE_2)
AUST_LOCALITY_POLYGON_May16 (writer ESRISHAPE_2)
    attributes: LOC_PID char(15), DT_CREATE date, DT_RETIRE date, NAME char(100), LOCCL_CODE char(1), DT_GAZETD date, POSTCODE char(4), PRIM_PCODE char(4), STATE_PID char(15)
